RedeemCheque

DEFINITIONS ::=
BEGIN

IMPORTS
    MyAttestation
        FROM AttestationFramework
    SignedCheque
        FROM SignedCheque
    Proof
        FROM ProofOfExponent;

RedeemCheque ::= SEQUENCE {
    signedCheque         SignedCheque,
    attestation          MyAttestation,
    proof                Proof,
    signatureValue       BIT STRING 
}

END
