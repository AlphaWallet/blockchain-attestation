UseDevconTicket

DEFINITIONS ::=
BEGIN

IMPORTS
    MyAttestation
        FROM AttestationFramework
    SignedDevconTicket
        FROM SignedDevconTicket
    Proof
        FROM ProofOfExponent;

UseDevconTicket ::= SEQUENCE {
    signedDevconTicket         SignedDevconTicket,
    attestation          MyAttestation,
    proof                Proof,
    signatureValue       BIT STRING
}

END
